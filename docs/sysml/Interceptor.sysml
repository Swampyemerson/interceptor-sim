// =============================================================================
// Interceptor.sysml -- the lean section-0c ram interceptor (Tier 2): Source One
// V6 airframe, Pixhawk 6C Mini on PX4, Raspberry Pi 5 + OV9281 seeker, ELRS
// kill/arm-only RC. No datalink after launch (constraint no-datalink).
//
// Two independent power rails (the two-rail rule): PM02 -> flight controller,
// Matek BEC -> Raspberry Pi. The Pi is never powered from the FC's rail.
// The brain-bench wires (6C Mini <-> Pi on TELEM2, M10 on GPS1) are
// `verified` -- they were proven on the bench and move onto the airframe as
// built. Everything that needs the airframe is `planned` until afr-01..05.
// =============================================================================
package Interceptor {
    doc /* Physical architecture of the interceptor. */

    private import HardwareLibrary::*;
    private import Components::*;

    part def InterceptorDrone {
        doc /* PX4 5-inch quad carrying a Pi 5 seeker; ram vehicle. */

        // ---------------------------------------------------------- parts
        part battery : LiPo6S1500 {
            doc /* Shared 6S pack pool with the target. */
            @BOM { tab = "target"; bomName = "CNHL 6S 1500"; }
            @Layout { col = 0; row = 0; }
        }
        part pm02 : PM02V3 {
            @BOM { tab = "airframe"; bomName = "Holybro PM02 V3"; }
            @Layout { col = 1; row = 0; }
        }
        part esc : KO60IIESC {
            @BOM { tab = "airframe"; bomName = "KO60II"; }
            @Layout { col = 2; row = 0; }
        }
        part motors : EcoII2207 [4] {
            doc /* 5 ordered: 4 flight + 1 spare shared with the target. */
            @BOM { tab = "airframe"; bomName = "EMAX ECO II 2207"; }
            @Layout { col = 3; row = 0; }
        }
        part props : HQV2S5in [4] {
            @BOM { tab = "airframe"; bomName = "HQProp V2S"; }
            @Layout { col = 4; row = 0; }
        }
        part fcSd : MicroSDCard {
            doc /* ULogs are the kill metrology -- no card, no scored flight. */
            @BOM { tab = "airframe"; bomName = "FC High-Endurance microSD"; }
            @Layout { col = 0; row = 1; }
        }
        part fc : Pixhawk6CMini {
            @BOM { tab = "brain"; bomName = "Pixhawk 6C Mini"; }
            @Layout { col = 1; row = 1; }
        }
        part gps : HolybroM10 {
            @BOM { tab = "brain"; bomName = "Holybro M10 GPS"; }
            @Layout { col = 2; row = 1; }
        }
        part airframe : SourceOneV6 {
            @BOM { tab = "airframe"; bomName = "TBS Source One V6"; }
            @Layout { col = 3; row = 1; }
        }
        part bec : MatekBEC12SPro {
            @BOM { tab = "airframe"; bomName = "Matek 12S Pro BEC"; }
            @Layout { col = 0; row = 2; }
        }
        part pi : RaspberryPi5 {
            doc /* The same board as the Tier-1 seeker rig, moved onto the airframe. */
            @BOM { tab = "seeker"; bomName = "Raspberry Pi 5"; }
            @Layout { col = 1; row = 2; }
        }
        part rx : RP3Diversity {
            @BOM { tab = "airframe"; bomName = "RP3 ELRS"; }
            @Layout { col = 2; row = 2; }
        }
        part finder : FlywooFinderV1 {
            @BOM { tab = "ground"; bomName = "Flywoo Finder"; }
            @Layout { col = 3; row = 2; }
        }
        part railCap : RailCap1000uF {
            @BOM { tab = "airframe"; bomName = "1000 uF"; }
            @Layout { col = 0; row = 3; }
        }
        part camera : OV9281Camera {
            @BOM { tab = "seeker"; bomName = "OV9281"; }
            @Layout { col = 1; row = 3; }
        }
        part piSd : MicroSDCard {
            doc /* Pi OS + timestamped raw frames. */
            @BOM { tab = "seeker"; bomName = "SanDisk 128 GB"; }
            @Layout { col = 2; row = 3; }
        }
        part cooler : PiActiveCooler {
            @BOM { tab = "seeker"; bomName = "active cooler"; }
            @Layout { col = 3; row = 3; }
        }
        part cameraMount : NoseCameraMount {
            @BOM { tab = "airframe"; bomName = "Nose-cantilever"; }
            @Layout { col = 4; row = 3; }
        }

        // ---------------------------------------------------------- power: flight rail
        interface mainPower : DCPowerLink connect battery.main to pm02.battIn {
            attribute :>> connector = "XT60";
            attribute :>> detail = "6S main power into the power module; flown 2026-11-09";
            attribute :>> linkState = LinkState::wired;
        }
        interface escPower : DCPowerLink connect pm02.battOut to esc.batt {
            attribute :>> connector = "XT60 pigtail, 14 AWG";
            attribute :>> detail = "PM02 pass-through to the ESC pads";
            attribute :>> linkState = LinkState::wired;
        }
        interface motorLeads : PhaseLink connect esc.motorOut to motors.phase {
            attribute :>> connector = "3-phase leads, soldered";
            attribute :>> detail = "4 channels; flown 2026-11-09 on the quad-X layout (airframe 4001, ADR-0134)";
            attribute :>> linkState = LinkState::wired;
        }
        interface fcPower : PowerModuleLink connect pm02.fcLead to fc.power1 {
            attribute :>> connector = "6-pin JST-GH";
            attribute :>> detail = "5.2 V + analog V/I sense to POWER1";
            attribute :>> linkState = LinkState::wired;
        }

        // ---------------------------------------------------------- power: Pi rail
        interface becFeed : DCPowerLink connect battery.main to bec.vin {
            attribute :>> connector = "16 AWG tap on the main leads";
            attribute :>> detail = "LiPo main straight to the BEC -- second rail";
            attribute :>> linkState = LinkState::wired;
        }
        interface piRail : DCPowerLink connect bec.out5v to pi.pwrIn {
            attribute :>> connector = "USB-C pigtail into the Pi's power port";
            attribute :>> detail = "entry point DECIDED: USB-C; 5.3 V steady at the Pi end by multimeter";
            attribute :>> linkState = LinkState::verified;
            attribute :>> evidence = "bench 2026-10-17";
        }
        interface railSmoothing : DCPowerLink connect bec.out5v to railCap.rail {
            attribute :>> connector = "soldered across the BEC 5 V output pads, in parallel with the pigtail";
            attribute :>> detail = "1000 uF 16 V electrolytic (kit cap); polarity + 5 V-side checked before power";
            attribute :>> linkState = LinkState::verified;
            attribute :>> evidence = "bench 2026-10-17";
        }
        interface fan : FanLink connect pi.fanHeader to cooler.header {
            attribute :>> connector = "4-pin fan header";
            attribute :>> detail = "5 V + PWM + tach";
            attribute :>> linkState = LinkState::verified;
            attribute :>> evidence = "skr-07";
        }

        // ---------------------------------------------------------- data
        interface escSignal : DShotLink connect fc.mainOut to esc.signal {
            attribute :>> connector = "signal lead (pin map TBD)";
            attribute :>> detail = "NOT DShot: plain PWM on MAIN 1-4, 400 Hz, 1100-1900 us (live board read 2026-11-09). MAIN cannot speak DShot; ledger interceptor-esc-protocol-pwm-not-dshot";
            attribute :>> linkState = LinkState::wired;
        }
        interface gpsCable : GPSCableLink connect fc.gps1 to gps.fcConn {
            attribute :>> connector = "10-pin JST-GH";
            attribute :>> detail = "GPS UART (UBX 10 Hz) + IST8310 compass on GPS1's own I2C + 5 V";
            attribute :>> linkState = LinkState::verified;
            attribute :>> evidence = "brn-02";
        }
        interface companion : UARTLink connect fc.telem2 to pi.gpioUart {
            @BOM { tab = "brain"; bomName = "Pi-to-TELEM2"; }
            attribute :>> connector = "JST-GH 6-pin -> JST-SH 3-pin (3 wires)";
            attribute :>> detail = "MAVLink 921600 on the Pi 5's 3-pin serial socket (/dev/ttyAMA10): TELEM2 pin2 TX -> socket pin 1 RX, pin3 RX <- socket pin 3 TX, pin6 GND -> socket pin 2; +5 V NOT connected";
            attribute :>> linkState = LinkState::verified;
            attribute :>> evidence = "runs/link_ttyAMA10_20261113";
        }
        interface rcSbus : RCInLink connect fc.rcIn to rx.fcConn {
            attribute :>> connector = "RC IN socket";
            attribute :>> detail = "SBUS (ELRS flashed to SBUS out) + 5 V; kill/arm only";
            attribute :>> linkState = LinkState::wired;
        }
        interface buzzer : BuzzerLink connect fc.buzzerTap to finder.fcConn {
            attribute :>> connector = "TBD";
            attribute :>> detail = "drive pin UNRESOLVED -- the 6C Mini has no buzzer pad";
            attribute :>> linkState = LinkState::wired;
        }
        interface ulogCard : SDCardLink connect fc.sdSlot to fcSd.contacts {
            attribute :>> connector = "onboard microSD slot";
            attribute :>> detail = "PX4 ULogs -- SLOT DEAD: no onboard logs; substitute is hover_recorder.py on the Pi";
            attribute :>> linkState = LinkState::wired;
        }
        interface cameraRibbon : CSI2Link connect camera.csi to pi.cam0 {
            @BOM { tab = "seeker"; bomName = "Wonrabai"; }
            attribute :>> connector = "22-to-15-pin CSI ribbon";
            attribute :>> detail = "MIPI CSI-2 into CAM/DISP0; 1280 x 800 mono. Verified on the first Pi (skr-02). On the replacement Pi this socket now holds the AR0234, working at 1920 x 1200 (2026-11-13), not this camera";
            attribute :>> linkState = LinkState::planned;
        }
        interface frameCard : SDCardLink connect pi.sdSlot to piSd.contacts {
            attribute :>> connector = "Pi microSD slot";
            attribute :>> detail = "Pi OS + raw PNG frames";
            attribute :>> linkState = LinkState::verified;
            attribute :>> evidence = "skr-01, skr-05";
        }

        // ---------------------------------------------------------- mechanical
        interface motorMounts : MountLink connect airframe.arms to motors.base {
            attribute :>> connector = "M3x8 screws";
            attribute :>> detail = "flown 2026-11-09";
            attribute :>> linkState = LinkState::wired;
        }
        interface propShafts : MountLink connect motors.shaft to props.hub {
            attribute :>> connector = "M5 shaft + nyloc";
            attribute :>> detail = "flown 2026-11-09";
            attribute :>> linkState = LinkState::wired;
        }
        interface escMount : MountLink connect airframe.stack to esc.standoffs {
            attribute :>> connector = "30 mm standoffs";
            attribute :>> detail = "insulate the frame under every board (carbon conducts)";
            attribute :>> linkState = LinkState::wired;
        }
        interface fcMount : MountLink connect airframe.stack to fc.softMount {
            attribute :>> connector = "vibration mount";
            attribute :>> detail = "flown 2026-11-09; FC mounted arrow-aft (SENS_BOARD_ROT=4)";
            attribute :>> linkState = LinkState::wired;
        }
        interface gpsMast : MountLink connect airframe.topPlate to gps.mast {
            attribute :>> connector = "short mast";
            attribute :>> detail = "compass away from power leads";
            attribute :>> linkState = LinkState::planned;
        }
        interface piTray : MountLink connect airframe.topPlate to pi.standoffs {
            @BOM { tab = "airframe"; bomName = "M2.5 nylon standoff"; }
            attribute :>> connector = "printed tray + M2.5 nylon standoffs";
            attribute :>> linkState = LinkState::planned;
        }
        interface noseMount : MountLink connect airframe.nose to cameraMount.frameFoot {
            attribute :>> connector = "nose cantilever";
            attribute :>> detail = "corner-spin prop-clearance gate at loaded throttle (afr-05)";
            attribute :>> linkState = LinkState::planned;
        }
        interface cameraSeat : MountLink connect cameraMount.cameraSeat to camera.mount {
            attribute :>> connector = "adjustable 10-30 deg bracket";
            attribute :>> detail = "angle locked from the first dash ULog";
            attribute :>> linkState = LinkState::planned;
        }
        interface batteryStrap : MountLink connect airframe.batteryPad to battery.strap {
            attribute :>> connector = "strap";
            attribute :>> detail = "battery rides underneath; flown 2026-11-09";
            attribute :>> linkState = LinkState::wired;
        }
    }
}
